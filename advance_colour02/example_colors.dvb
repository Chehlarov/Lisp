Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True

Sub Change_Layers()
    ' This example finds the current Layers collection and
    ' adds a new layer to that collection.
    
    Dim count As Integer
    count = ThisDrawing.ModelSpace.count
    
    Dim color_obj As AcadAcCmColor
    Dim layer_obj As AcadLayer
    
    ReDim newobjs(count) As AcadEntity
    Dim index As Integer
    For index = 0 To count - 1
        Set newobjs(index) = ThisDrawing.ModelSpace.Item(index)
        Set color_obj = newobjs(index).TrueColor
        
        '102
        If (color_obj.Red = 0) And (color_obj.Green = 204) And (color_obj.Blue = 51) Then
        newobjs(index).Layer = "STR_POUTRES"
        newobjs(index).color = acByLayer
        End If
        'magenta
        If (color_obj.Red = 255) And (color_obj.Green = 0) And (color_obj.Blue = 255) Then
        newobjs(index).Layer = "STR_VOILES"
        newobjs(index).color = acByLayer
        End If
        
        '103
        If (color_obj.Red = 102) And (color_obj.Green = 204) And (color_obj.Blue = 127) Then
        newobjs(index).Layer = "STR_DALLES"
        newobjs(index).color = acByLayer
        End If
        
        '11
        If (color_obj.Red = 255) And (color_obj.Green = 127) And (color_obj.Blue = 127) Then
        newobjs(index).Layer = "STR_RESV_DALLE"
        newobjs(index).color = acByLayer
        End If
        
        '60
        If (color_obj.Red = 197) And (color_obj.Green = 255) And (color_obj.Blue = 0) Then
        newobjs(index).Layer = "STR_BET VU"
        newobjs(index).color = acByLayer
        End If
        
        '?????????????
        'If (color_obj.Red = 255) And (color_obj.Green = 0) And (color_obj.Blue = 255) Then
        'newobjs(index).Layer = "STR_VOI-POT"
        'newobjs(index).color = acByLayer
        'End If
        
        '141
        If (color_obj.Red = 127) And (color_obj.Green = 223) And (color_obj.Blue = 255) Then
        newobjs(index).Layer = "STR_BET_CACHE"
        newobjs(index).color = acByLayer
        End If
        
        '9
        If (color_obj.Red = 192) And (color_obj.Green = 192) And (color_obj.Blue = 192) Then
        newobjs(index).Layer = "STR_SURCH"
        newobjs(index).color = acByLayer
        End If
        
        'cyan
        If (color_obj.Red = 0) And (color_obj.Green = 255) And (color_obj.Blue = 255) Then
        newobjs(index).Layer = "STR_AXES"
        newobjs(index).color = acByLayer
        End If
        
        'red
        If (color_obj.Red = 255) And (color_obj.Green = 0) And (color_obj.Blue = 0) Then
        newobjs(index).Layer = "STR_AXES_REPERE"
        newobjs(index).color = acByLayer
        End If
        
        '30
        If (color_obj.Red = 255) And (color_obj.Green = 127) And (color_obj.Blue = 0) Then
        newobjs(index).Layer = "STR_COTATION"
        newobjs(index).color = acByLayer
        End If
        
        '120
        If (color_obj.Red = 0) And (color_obj.Green = 255) And (color_obj.Blue = 191) Then
        newobjs(index).Layer = "STR_TXT"
        newobjs(index).color = acByLayer
        End If
        
         '161
        If (color_obj.Red = 127) And (color_obj.Green = 159) And (color_obj.Blue = 255) Then
        newobjs(index).Layer = "STR_OPENING"
        newobjs(index).color = acByLayer
        End If
        
        'MsgBox "Red = " & color_obj.Red
        'MsgBox "Green = " & color_obj.Green
        'MsgBox "Blue = " & color_obj.Blue
    Next

    
End Sub
