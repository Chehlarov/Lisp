(defun c:dupfr()
  (setq p1 (getpoint " "))
  (setq p2 (getpoint p1))
  (setq dist (distance p1 p2))
  (print dist)
  (print )
  (setq as (getreal "cm2/m "))
  ;(setq span (getint "span: "))
  (setq areastopped (* as  dist))
  (setq areareplaement (* 0.5 areastopped))
  (print "0.5As = От всяка страна на дупката = ")
  (princ areareplaement)
  (princ)
  )
