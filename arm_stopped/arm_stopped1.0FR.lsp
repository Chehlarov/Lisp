(defun c:dup()
  (setq p1 (getpoint " "))
  (setq p2 (getpoint p1))
  (setq dist (distance p1 p2))
  (print dist)
  (print )
  (setq as (getreal "cm2/m "))
  ;(setq span (getint "span: "))
  (setq areastopped (* as  dist))
  (setq areareplaement (* 0.5 areastopped))
  (print "От всяка страна на дупката ")
  (princ areareplaement)
  (princ)
  )

(defun c:us()
  (setq p1 (getpoint " "))
  (setq p2 (getpoint p1))
  (setq dist (distance p1 p2))
  (print dist)
  (setq diam (getint "diam: "))
  (setq span (getint "span: "))
  (setq areastopped (* (/ (* pi diam diam) 400) (/ dist span) ))
  (setq areareplaement (* 0.3 areastopped))
  (print "За усилента ивица ")
  (princ areareplaement)
  (princ)
  )
